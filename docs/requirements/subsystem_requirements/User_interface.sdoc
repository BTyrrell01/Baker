[DOCUMENT]
TITLE: Electrical Subsystem: User Interface
VERSION: @GIT_BRANCH

[TEXT]
STATEMENT: >>>
**Scope**: The user interface subsystem includes the display, the buttons and the speaker.

**Display**: What the user looks at to get information directly from the watch

**Buttons**: What the user uses to control the watch
<<<

[[SECTION]]
TITLE: Requirements

[REQUIREMENT]
UID: REQ-19
STATUS: Active
TITLE: Display visibility
STATEMENT: >>>
The display shall be visible in outdoor environments, as well as at night.
<<<
RELATIONS:
- TYPE: Parent
  VALUE: MOE-001-001

[REQUIREMENT]
UID: REQ-20
STATUS: Active
TITLE: Buttons
STATEMENT: >>>
The device shall not miss (or misinterpret) more than 1ppm of button presses
<<<
RELATIONS:
- TYPE: Parent
  VALUE: MOE-001-008

[REQUIREMENT]
UID: REQ-24
TITLE: Display refresh rate
STATEMENT: >>>
Display shall refresh at 60FPS.
<<<
RATIONALE: >>>
Animations must look smooth and crisp.
<<<

[[/SECTION]]
